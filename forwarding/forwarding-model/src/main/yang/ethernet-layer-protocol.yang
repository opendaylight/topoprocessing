module ethernet-layer-protocol {
    namespace "urn:opendaylight:logicalterminationpoint:ethernet";
    prefix ethernet-lp;

    import logical-termination-point {prefix ltp; revision-date "2015-02-18";}
    import ietf-yang-types {prefix yang; revision-date "2010-09-24";}
    import opendaylight-queue-types {prefix queue-types; revision-date "2013-09-25";}

    revision "2015-02-18" {
        description "Initial revision of the Ethernet Layer Protocol model";
    }

    grouping ethernet-layer-protocol-type {
        container ethernet-layer-protocol {
            presence "indicates Ethernet Layer Protocol";
        }
    }

    typedef port-features {
        type bits {
            bit ten-mb-hd;
            bit ten-mb-fd;
            bit hundred-mb-hd;
            bit hundred-mb-fd;
            bit one-gb-hd;
            bit one-gb-fd;
            bit ten-gb-fd;
            bit forty-gb-fd;
            bit hundred-gb-fd;
            bit one-tb-fd;
            bit other;
            bit copper;
            bit fiber;
            bit autoeng;
            bit pause;
            bit pause-asym;
        }
    }

    grouping queues {
        list queue {
            key "queue-id";
            uses queue-types:queue-packet;
        }
    }

    grouping ethernet-lp-attributes {
        leaf hardware-address {
            type yang:mac-address;
            description "MAC Address of the port";
        }

        leaf current-feature {
            type port-features;
            description "Bit map of OFPPF-* flags";
        }

        leaf supported {
            type port-features;
            description "Features supported by the port";
        }

        leaf peer-features {
            type port-features;
            description "Features advertised by peer";
        }

        leaf advertised-features {
            type port-features;
            description "Features being advertised by the port";
        }

        leaf current-speed {
            type uint32;
            units "kbps";
            description "Current port bit rate in kbps";
        }

        leaf maximum-speed {
            type uint32;
            units "kbps";
            description "Max port bit rate in kbps";
        }

        uses queues;
    }

    augment "/ltp:logical-termination-point/ltp:layer-protocol-types" {
        uses ethernet-layer-protocol-type;
    }

    augment "/ltp:logical-termination-point/ltp:layer-protocol-attributes" {
        when "ltp:logical-termination-point/ethernet-layer-protocol";
        uses ethernet-lp-attributes;
    }

}
