module multilayer-topology {
    yang-version 1;
    namespace "urn:opendaylight:topology:multilayer";
    prefix "ml";

    import yang-ext         { prefix "ext";   revision-date 2013-07-09; }

    import ietf-inet-types  { prefix "inet";  revision-date 2013-07-15; }
    import network-topology { prefix "nt";    revision-date 2013-10-21; }
    import multitechnology-topology
                            { prefix "mt";    revision-date 2015-01-22; }

    organization "Ericsson AB";
    contact "carlo.perocchio@ericsson.com
             Ericsson
             Via Melen, 77
             Genoa - 16152
             Italy";

    description
        "
        Copyright (c) 2015 Ericsson, AB.  All rights reserved.

        This program and the accompanying materials are made available
        under the terms of the Eclipse Public License v1.0 which
        accompanies this distribution, and is available at
        http://www.eclipse.org/legal/epl-v10.html

        This module introduces multilayer using forwarding adjacency concept
        in network-topology for a SDN context.";

    revision "2015-01-23" {
        description
            "Initial revision.";
    }

    grouping multilayer-topology-type {
        container multilayer-topology {
            presence
                "Indicates a multilayer topology based on forwarding adjacency.";
        }
    }

    augment "/nt:network-topology/nt:topology/nt:topology-types/mt:multitechnology-topology" {
        ext:augment-identifier "ml-topology-type";
        uses multilayer-topology-type;
    }

    //
    // As in: bgpcep/topology/api/src/main/yang/odl-network-topology.yang
    //
    identity multilayer-topology-context {
        description
            "Identity used to mark the multilayer network topology context.
             Defined for RPC binding to a particular topology instance.
             The instance must support Multilayer RPCs.";
    }

    typedef network-topology-ref {
        type instance-identifier;
        ext:context-reference "multilayer-topology-context";
    }

    grouping network-topology-reference {
        leaf network-topology-ref {
            type network-topology-ref;
            mandatory true;
            ext:context-reference "multilayer-topology-context";
        }
    }

    augment "/nt:network-topology/nt:topology" {
        ext:context-instance "multilayer-topology-context";
    }

    typedef fa-id {
        type inet:uri;
        description
            "A unique identifier used by RPC to refer to an existing forwarding adjacency.";
    }

    grouping fa-end-point {
        leaf node {
            mandatory true;
            type nt:node-ref;
            description "Network node end point.";
        }
        leaf-list supporting-tp {
            type nt:tp-ref;
            description
                "List of termination points that support end point TP.
                If forwarding adjacency announcement triggers termination point
                creation, this list is used to fill tp-ref attribute.";
        }
        leaf tp-id {
            type nt:tp-id;
            description
                "Forwarding adjacency interface unique identifier.
                If forwarding adjacency announcement triggers termination point
                creation, this id is used for TP creation.";
        }
        container stitching-point {
            description
                "Traffic patch to end-point.
                If present, forwarding adjacency announcement refers to a FA segment.
                If present, termination point may not be created.";
            leaf-list supporting-tp {
                description
                    "List of termination points that support stiching point TP.
                    If forwarding adjacency announcement triggers termination point
                    creation, this list is used to fill tp-ref attribute.";
                type nt:tp-ref;
            }
            leaf tp-id {
                description
                    "Forwarding adjacency stitching TP unique identifier.";
                type nt:tp-id;
            }
        }
        uses mt:mt-info {
            description "End-point multitechnology traffic engineering parameters.";
        }
    }

    grouping fa-parameters {

        choice directionality-info {
            case unidirectional {
                description "Forwarding adjacency is unidirectional.";
                container unidirectional {
                }
            }
            case reverse-fa {
                description "Forwarding adjacency has a reverse forwarding adjacency";
                container reverse-fa {
                }
            }
            case reverse-co-routed-fa {
                description "Forwarding adjacency has a reverse co-routed forwarding adjacency";
                container reverse-co-routed-fa {
                }
            }
            case bidirectional {
                description "Forwarding adjacency is bidirectional, announcements updates will reflect on both directions.";
                container bidirectional {
                }
            }
        }
        uses mt:mt-info {
            description "Link multitechnology traffic engineering parameters used in case of link creation.";
        }
    }

    typedef fa-oper-status {
        description "Providing the type definition of the forwarding adjacency operative status
                     based on a subset of all potential values in general.";
        type enumeration {
            enum up {
               value 1;
               description
                 "The forwarding adjacency is ready to pass traffic";
            }
            enum down {
                value 2;
                description
                 "The forwarding adjacency is not ready to pass traffic";
            }
        }
    }

    grouping oper-status {
        leaf oper-status {
            type fa-oper-status;
            description "Forwarding adjacency operative status.";
        }
    }

    grouping forwarding-adjacency-attributes {

        container head-end {
            description "Head-point description of the forwarding adjacency.";
            uses fa-end-point;
        }
        container tail-end {
            description "Tail-point description of the forwarding adjacency.";
            uses fa-end-point;
        }

        uses fa-parameters;
        uses oper-status;

        container announcement-context {
            description "Optional information";
            leaf id {
                type inet:uri;
                description
                    "An identifier for the entity announcing/providing
                     forwarding adjacency.";
            }
            list supporting-resource {
                ordered-by user;
                key "resource";
                leaf resource {
                    description
                        "An ordered list from head-end to tail-end of
                         supporting resources.";
                    type instance-identifier;
                }
            }
        }
    }

    grouping fa-stitched-end-point {
        leaf node {
            mandatory true;
            type nt:node-id;
            description "Forwarding adjacency node end point identifier resulting afterwards stiching occured";
        }
        leaf tp-id {
            description "Forwarding adjacency stitching TP unique identifier resulting afterwards stiching occured";
            type nt:tp-id;
        }
    }

    grouping fa-stitched-end-point-pair {
        container stitched-head-end {
            uses fa-stitched-end-point;
        }
        container stitched-tail-end {
            uses fa-stitched-end-point;
        }
    }

    rpc forwarding-adj-announce {
        input {
            uses network-topology-reference {
                description
                    "The context of the announcement:
                     the network topology where forwarding adjacency is announced.";
            }
            uses forwarding-adjacency-attributes;
        }
        output {
            choice result {
                case fa-id {
                    leaf fa-id {
                        type fa-id;
                    }
                    uses fa-stitched-end-point-pair;
                }
                case none {
                    leaf none {
                        type empty;
                    }
                }
            }
        }
    }

    rpc forwarding-adj-withdraw {
        input {
            uses network-topology-reference {
                description
                    "The network topology where to apply the withdrawal, the
                     same to which forwarding adjacency has been announced.";
            }
            leaf fa-id {
                type fa-id;
            }
        }
        output {
            choice result {
                case ok {
                    leaf ok {
                        type empty;
                    }
                }
                case error {
                    container error {
                    }
                }
            }
        }
    }

    rpc forwarding-adj-update {
        input {
            uses network-topology-reference {
                description
                    "The network topology to which forwarding adjacency has
                     been announced.";
            }
            leaf fa-id {
                type fa-id;
            }
            uses forwarding-adjacency-attributes;
        }
        output {
            choice result {
                case ok {
                    leaf ok {
                        type empty;
                    }
                }
                case error {
                    container error {
                    }
                }
            }
        }
    }
}
