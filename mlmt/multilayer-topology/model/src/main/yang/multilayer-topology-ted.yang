module multilayer-topology-ted {
    yang-version 1;
    namespace "urn:opendaylight:topology:multilayer:ted";
    prefix "mlted";

    import yang-ext         { prefix "ext";   revision-date 2013-07-09; }
    import ted              { prefix "ted";   revision-date 2013-10-21; }
    import multitechnology-topology-ted
                            { prefix "mted";  revision-date 2015-01-22; }
    import multilayer-topology
                            { prefix "ml";    revision-date 2015-01-23; }

    organization "Ericsson AB";
    contact "carlo.perocchio@ericsson.com
             Ericsson
             Via Melen, 77
             Genoa - 16152
             Italy";

    description
        "
        Copyright (c) 2015 Ericsson, AB.  All rights reserved.

        This program and the accompanying materials are made available
        under the terms of the Eclipse Public License v1.0 which
        accompanies this distribution, and is available at
        http://www.eclipse.org/legal/epl-v10.html

        This module introduces multilayer using forwarding adjacency concept 
        in network-topology for a SDN context.";

    revision "2015-01-23" {
        description
            "Initial revision.";
    }

    augment "/ml:forwarding-adj-announce/ml:input/ml:attribute/ml:value" {
        when "./ml:attribute-type = 'mted:native-l3-igp-metric' or " +
             "./ml:attribute-type = 'mted:controller-metric' or " +
             "./ml:attribute-type = 'mted:application-metric'";
        ext:augment-identifier "mlted-fa-announce-metric-attr";
        leaf metric {
            type uint32;
        }
    }

    augment "/ml:forwarding-adj-update/ml:input/ml:attribute/ml:value" {
        when "./ml:attribute-type = 'mted:native-l3-igp-metric' or " +
             "./ml:attribute-type = 'mted:controller-metric' or " +
             "./ml:attribute-type = 'mted:application-metric'";
        ext:augment-identifier "mlted-fa-update-metric-attr";
        leaf metric {
            type uint32;
        }
    }

    augment "/ml:forwarding-adj-announce/ml:input/ml:attribute/ml:value" {
        when "./ml:attribute-type = 'mted:native-ted' or " +
             "./ml:attribute-type = 'mted:controller-ted' or " +
             "./ml:attribute-type = 'mted:application-ted'";
        ext:augment-identifier "mlted-fa-announce-link-attr";
        uses ted:ted-link-attributes;
    }

    augment "/ml:forwarding-adj-update/ml:input/ml:attribute/ml:value" {
        when "./ml:attribute-type = 'mted:native-ted' or " +
             "./ml:attribute-type = 'mted:controller-ted' or " +
             "./ml:attribute-type = 'mted:application-ted'";
        ext:augment-identifier "mlted-fa-update-link-attr";
        uses ted:ted-link-attributes;
    }
}
