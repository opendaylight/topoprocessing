module mlmt-topology-observer {
    yang-version 1;
    namespace "urn:opendaylight:topology:mlmt-topology-observer";
    prefix "mlmt-obs";

    organization "Ericsson AB";
    contact "TBD";

    description
       "Copyright (c) 2015 Ericsson, AB.  All rights reserved.

        This program and the accompanying materials are made available
        under the terms of the Eclipse Public License v1.0 which
        accompanies this distribution, and is available at
        http://www.eclipse.org/legal/epl-v10.html";

    revision "2015-01-22" {
        description
            "Initial revision.";
        reference "";
    }
}
