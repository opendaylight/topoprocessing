module mlmt-observer-impl {

    yang-version 1;
    namespace "urn:opendaylight:topology:mlmt-topology-observer:impl";
    prefix "mlmt-obs-impl";

    import config { prefix config; revision-date 2013-04-05; }
    import rpc-context { prefix rpcx; revision-date 2013-06-17; }
    import opendaylight-md-sal-binding { prefix mdsal; revision-date 2013-10-28; }

    description
        "This module contains the base YANG definitions for
        mlmt-topology-observer impl implementation.";

    revision "2015-01-22" {
        description
            "Initial revision.";
    }

    // This is the definition of the service implementation as a module identity.
    identity mlmt-topology-observer-impl {
            base config:module-type;

            // Specifies the prefix for generated java classes.
            config:java-name-prefix MlmtTopologyObserver;
    }

    // Augments the 'configuration' choice node under modules/module.
    augment "/config:modules/config:module/config:configuration" {
        case mlmt-topology-observer-impl {
            when "/config:modules/config:module/config:type = 'mlmt-topology-observer-impl'";

            container rpc-registry {
                uses config:service-ref {
                    refine type {
                        mandatory true;
                        config:required-identity mdsal:binding-rpc-registry;
                    }
                }
            }

            container notification-service {
                uses config:service-ref {
                    refine type {
                        mandatory true;
                        config:required-identity mdsal:binding-notification-service;
                    }
                }
            }

            container data-broker {
                uses config:service-ref {
                    refine type {
                        mandatory false;
                        config:required-identity mdsal:binding-async-data-broker;
                    }
                }
            }
        }
    }

    augment "/config:modules/config:module/config:state" {
        case mlmt-topology-observer-impl {
            when "/config:modules/config:module/config:type = 'mlmt-topology-observer-impl'";
        }                    
    }
}
