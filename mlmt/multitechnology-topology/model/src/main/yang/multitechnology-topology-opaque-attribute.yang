module multitechnology-topology-opaque-attribute {
    yang-version 1;
    namespace "urn:opendaylight:topology:multitechnology:opaque-attribute";
    prefix "mtoa";

    import yang-ext                 { prefix "ext";   revision-date 2013-07-09; }

    import network-topology         { prefix "nt";    revision-date 2013-10-21; }
    import multitechnology-topology { prefix "mt";    revision-date 2015-01-22; }

    organization "Ericsson AB";
    contact "carlo.perocchio@ericsson.com
             Ericsson
             Via Melen, 77
             Genoa - 16152 
             Italy";

    description
        "
        Copyright (c) 2015 Ericsson, AB.  All rights reserved.

        This program and the accompanying materials are made available
        under the terms of the Eclipse Public License v1.0 which
        accompanies this distribution, and is available at
        http://www.eclipse.org/legal/epl-v10.html

        This module defines attribute value augmentation of multitechnology
        network topology in order to introduce the ability to represent any
        'basic' application defined parameter without requesting changes to
        to controller.";

    revision "2015-01-22" {
        description
            "Initial revision.";
    }

    grouping multitechnology-topology-opaque-attribute-type {
        container multitechnology-opaque-attribute-topology {
            presence "indicates normalized Multi-Technology Topology supporting opaque attributes.";
        }
    }

    augment "/nt:network-topology/nt:topology/nt:topology-types/mt:multitechnology-topology" {
        ext:augment-identifier "mt-topology-opaque-attribute-type";
        uses multitechnology-topology-opaque-attribute-type;
    }

    //
    // General Purpose Attribute Container
    //
    identity native {
        description "native";
        base mt:base-attribute-type;
    }
    identity controller {
        description "controller";
        base mt:base-attribute-type;
    }
    identity application {
        description "application";
        base mt:base-attribute-type;
    }

    grouping opaque-attribute-value {
        choice basic-attribute-types {
            case boolean-value   { leaf      boolean-value   { type boolean; } }
            case empty-value     { leaf      empty-value     { type empty; } }
            case int32-value     { leaf      int64-value     { type int32; } }
            case string-value    { leaf      string-value    { type string; } }
            case string-list     { leaf-list string-list     { type string; } }
            case uint32-value    { leaf      uint32-value    { type uint32; } }
        }
    }

    augment "/nt:network-topology/nt:topology/nt:node/mt:attribute/mt:value" {
        when "./mt:attribute-type = 'native' or " +
             "./mt:attribute-type = 'controller' or " +
             "./mt:attribute-type = 'application'";
        ext:augment-identifier "mt-opaque-node-attribute-value";
        uses opaque-attribute-value;
    }
    augment "/nt:network-topology/nt:topology/nt:link/mt:attribute/mt:value" {
        when "./mt:attribute-type = 'native' or " +
             "./mt:attribute-type = 'controller' or " +
             "./mt:attribute-type = 'application'";
        ext:augment-identifier "mt-opaque-link-attribute-value";
        uses opaque-attribute-value;
    }

    augment "/nt:network-topology/nt:topology/nt:node/nt:termination-point/mt:attribute/mt:value" {
        when "./mt:attribute-type = 'native' or " +
             "./mt:attribute-type = 'controller' or " +
             "./mt:attribute-type = 'application'";
        ext:augment-identifier "mt-opaque-tp-attr-value";
        uses opaque-attribute-value;
    }
}
