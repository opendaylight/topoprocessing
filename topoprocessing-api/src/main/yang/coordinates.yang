/*
 * Copyright (c) 2015 Pantheon Technologies s.r.o. and others. All rights reserved.
 *
 * This program and the accompanying materials are made available under the
 * terms of the Eclipse Public License v1.0 which accompanies this distribution,
 * and is available at http://www.eclipse.org/legal/epl-v10.html
 */

module node-coordinates {

    namespace "urn:opendaylight:topology:node:coordinates";
    prefix "node-coordinates";

    import network-topology {prefix topo; revision-date "2013-10-21";}
    import ietf-inet-types {prefix inet;}
    import yang-ext {prefix ext; revision-date "2013-07-09";}

    revision "2015-10-08" {
    }

    augment "/topo:network-topology/topo:topology/topo:node" {
        ext:augment-identifier "node-coordinates-augment";
        uses node-coordinates-grouping;
    }

    grouping node-coordinates-grouping {
        leaf longitude {
            type string;
        }
        leaf latitude {
            type string;
        }
    }

}
