/*
 * Copyright (c) 2015 Pantheon Technologies s.r.o. and others. All rights reserved.
 *
 * This program and the accompanying materials are made available under the
 * terms of the Eclipse Public License v1.0 which accompanies this distribution,
 * and is available at http://www.eclipse.org/legal/epl-v10.html
 */

module topology-correlation {

    namespace "urn:opendaylight:topology:correlation";
    prefix "topo-correlation";

    import network-topology {prefix topo; revision-date "2013-10-21";}
    import ietf-inet-types {prefix inet; revision-date "2013-07-15";}
    import yang-ext {prefix ext; revision-date "2013-07-09";}
    import ietf-network {prefix i2rs; revision-date "2015-06-08";}

    revision "2015-01-21" {
        description "Topology Processing Framework correlation definition";
    }

    typedef leaf-path {
        description "Path to leaf that shall be compared.
        This definition should be tuned later.
        Something like RelativeSchemaPath might be useful.";
        type string;
    }

    typedef correlation-item-enum {
        description  "Supported corelation items";
        type enumeration {
            enum node {
                description "node";
            }
            enum link {
                description "link";
            }
            enum termination-point {
                description "termination-point";
            }
        }
    }

    identity model {
        description  "Base identity used for model differentiation";
    }
    
    identity network-topology-model {
        description "network-topology@2013-10-21.yang";
        base model;
    }

    identity opendaylight-inventory-model {
        description "opendaylight-inventory.yang";
        base model;
    }

    identity inventory-rendering-model {
        description "inventory-rendering.yang";
        base model;
    }

    identity i2rs-model {
        description "ietf-network@2015-06-08.yang";
        base model;
    }

    identity correlation-base {
        description "Base identity for correlation types";
    }

    identity aggregation-only {
        description "Aggregates node based on provided field.";
        base correlation-base;
    }

    identity filtration-only {
        description "Only nodes with specific leaf value will be present in overlay topology.";
        base correlation-base;
    }

    identity filtration-aggregation {
        description "Unification aggregation preceeded with filtration.";
        base correlation-base;
    }

    identity rendering-only {
        description "Creates nodes with augmented fields from another model.";
        base correlation-base;
    }

    identity aggregation-base {
        description "Base identity for aggregation types";
    }

    identity equality {
        description "Only aggregated correlation-items (nodes/links/termination points) will
                     be present in overlay topology.";
        base aggregation-base;
    }

    identity unification {
        description "All correlation-items (nodes/links/termination points) will be present
                     in overlay topology. Those that can be aggregated, will be aggregated";
        base aggregation-base;
    }

    identity filter-base {
        description "Base identity for filter types";
    }

    identity ipv4-address {
        description "Filters based on IPv4 address and mask.";
        base filter-base;
    }

    identity ipv6-address {
        description "Filters based on IPv6 address and mask.";
        base filter-base;
    }

    identity range-number {
        description "Filters filtering range of numbers between min and max value.";
        base filter-base;
    }

    identity range-string {
        description "Filters filtering range of strings between min and max value.";
        base filter-base;
    }

    identity specific-number {
        description "Filters out int values corresponding to a specific number.";
        base filter-base;
    }

    identity specific-string {
        description "Filters out string values corresponding to a specific string.";
        base filter-base;
    }

    identity script {
        description "Filters out string values corresponding to a specific string.";
        base filter-base;
    }

    augment "/topo:network-topology/topo:topology" {
        ext:augment-identifier "correlation-augment";
        uses correlations-grouping;
    }

    augment "/i2rs:network/" {
        ext:augment-identifier "i2rs-correlation-augment";
        uses correlations-grouping;
    }

    grouping correlations-grouping {
        container correlations {
            leaf output-model {
                type identityref {
                    base model;
                }
                description "Desired model for output from correlation.";
            }
            list correlation {
                key correlation-id;
                leaf correlation-id {
                    type string;
                    description "User defined content to uniquely identify the correlation. This value is not used for further processing.";
                }
                leaf type {
                    type identityref {
                        base correlation-base;
                    }
                }
                leaf correlation-item {
                    type correlation-item-enum;
                }
                container aggregation {
                    leaf aggregation-type {
                        type identityref {
                            base aggregation-base;
                        }
                    }
                    uses scripting-grouping;
                    list mapping {
                        key "underlay-topology";
                        uses input-model-grouping;
                        leaf underlay-topology {
                            type string;
                            description "Input topology which will be used for aggregation.";
                        }
                        list target-field {
                            key "target-field-path";
                            leaf target-field-path {
                                type leaf-path;
                                description "Path to target field";
                            }
                            leaf matching-key {
                                type uint16;
                                description "Which target-fields in different mappings should be compared";
                            }
                        }
                        leaf aggregate-inside {
                            type boolean;
                            mandatory true;
                            description "True if aggregation should happen even inside the same topology.";
                        }
                        leaf-list apply-filters {
                            type string;
                            description "Refers to filter-id of filter to be applied.";
                        }
                    }
                }
                container filtration {
                    leaf underlay-topology {
                        type string;
                        description "Input topology which will be filtered.";
                    }
                    list filter {
                        key "filter-id";
                        uses input-model-grouping;
                        leaf filter-id {
                            type string;
                        }
                        leaf filter-type {
                            type identityref {
                                base filter-base;
                            }
                        }
                        leaf target-field {
                            type leaf-path;
                            description "Path to target field";
                        }
                        choice filter-type-body {
                            case ipv4-address-filter-type {
                                container ipv4-address-filter {
	                                leaf ipv4-address {
	                                    type inet:ip-prefix;
	                                }
                                }
                            }
                            case ipv6-address-filter-type {
                                container ipv6-address-filter {
	                                leaf ipv6-address {
	                                    type inet:ip-prefix;
	                                }
                                }
                            }
                            case range-number-filter-type {
                                container range-number-filter {
                                    leaf min-number-value {
                                        type uint16;
                                    }
                                    leaf max-number-value {
                                        type uint16;
                                    }
                                }
                            }
                            case range-string-filter-type {
                                container range-string-filter {
                                    leaf min-string-value {
                                        type string;
                                    }
                                    leaf max-string-value {
                                        type string;
                                    }
                                }
                            }
                            case specific-number-filter-type {
                                container specific-number-filter {
	                                leaf specific-number {
	                                    type uint16;
	                                }
                                }
                            }
                            case specific-string-filter-type {
                                container specific-string-filter {
	                                leaf specific-string {
	                                    type string;
	                                }
                                }
                            }
                            case script-filter-type {
                                container script-filter {
                                    uses scripting-grouping;
                                }
                            }
                        }
                    }
                }
                container rendering {
                    leaf underlay-topology {
                        type string;
                        description "Input topology to render.";
                    }
                    uses input-model-grouping;
                }
            }
        }
    }

    grouping scripting-grouping {
        container scripting {
            leaf language {
                type string;
            }
            leaf script {
                type string;
            }
        }
    }

    grouping input-model-grouping {
        leaf input-model {
            type identityref {
                base model;
            }
            description "Specifies what structures, identifiers and QNames should be used.";
        }
    }
}
