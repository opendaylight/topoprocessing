module multitechnology-topology-ted {
    yang-version 1;
    namespace "urn:opendaylight:topology:multitechnology:ted";
    prefix "mted";

    import yang-ext                 { prefix "ext";   revision-date 2013-07-09; }

    import network-topology         { prefix "nt";    revision-date 2013-10-21; }
    import multitechnology-topology { prefix "mt";    revision-date 2015-01-22; }
    import ted                      { prefix "ted";   revision-date 2013-10-21; }

    organization "Ericsson AB";
    contact "TBD
             Ericsson
             Via Melen, 77
             Genoa - 16152 
             Italy";

    description
        "
        Copyright (c)2015 Ericsson, AB. All rights reserved.

        This program and the accompanying materials are made available
        under the terms of the Eclipse Public License v1.0 which
        accompanies this distribution, and is available at
        http://www.eclipse.org/legal/epl-v10.html

        This module introduces traffic engineering defined parameters in
        multitechnology network topology.";

    revision "2015-01-22" {
        description
            "Initial revision.";
    }

    grouping multitechnology-topology-ted-type {
        container multitechnology-ted-topology {
            presence "indicates normalized Multi-Technology Topology containing TE info";
        }
    }

    augment "/nt:network-topology/nt:topology/nt:topology-types/mt:multitechnology-topology" {
        ext:augment-identifier "mt-topology-ted-type";
        uses multitechnology-topology-ted-type;
    }

    //
    // Metric
    //
    identity native-l3-igp-metric {
        description "native routing metric";
        base mt:base-attribute-type;
    }
    identity controller-metric {
        description "controller chosen metric";
        base mt:base-attribute-type;
    }
    identity application-metric {
        description "metric required by application";
        base mt:base-attribute-type;
    }

    augment "/nt:network-topology/nt:topology/nt:node/mt:attribute/mt:value" {
        when "./mt:attribute-type = 'native-l3-igp-metric' or " +
             "./mt:attribute-type = 'controller-metric' or " +
             "./mt:attribute-type = 'application-metric'";
        ext:augment-identifier "mt-node-metric-attribute-value";
        leaf metric {
            type uint32;
        }
    }
    augment "/nt:network-topology/nt:topology/nt:link/mt:attribute/mt:value" {
        when "./mt:attribute-type = 'native-l3-igp-metric' or " +
             "./mt:attribute-type = 'controller-metric' or " +
             "./mt:attribute-type = 'application-metric'";
        ext:augment-identifier "mt-link-metric-attribute-value";
        leaf metric {
            type uint32;
        }
    }

    //
    // node TE and link TE
    //
    identity native-ted {
        description "native traffic engineering information";
        base mt:base-attribute-type;
    }
    identity controller-ted {
        description "controller traffic engineering information";
        base mt:base-attribute-type;
    }
    identity application-ted {
        description "application traffic engineering information";
        base mt:base-attribute-type;
    }

    augment "/nt:network-topology/nt:topology/nt:node/mt:attribute/mt:value" {
        when "./mt:attribute-type = 'native-ted' or " +
             "./mt:attribute-type = 'controller-ted' or " +
             "./mt:attribute-type = 'application-ted'";
        ext:augment-identifier "mt-ted-node-attribute-value";
        uses ted:ted-node-attributes;
    }
    augment "/nt:network-topology/nt:topology/nt:link/mt:attribute/mt:value" {
        when "./mt:attribute-type = 'native-ted' or " +
             "./mt:attribute-type = 'controller-ted' or " +
             "./mt:attribute-type = 'application-ted'";
        ext:augment-identifier "mt-ted-link-attribute-value";
        uses ted:ted-link-attributes;
    }
}
