/*
 * Copyright (c) 2015 Pantheon Technologies s.r.o. and others.  All rights reserved.
 *
 * This program and the accompanying materials are made available under the
 * terms of the Eclipse Public License v1.0 which accompanies this distribution,
 * and is available at http://www.eclipse.org/legal/epl-v10.html
 */

 module topoprocessing-nt-provider-impl {
    yang-version 1;
    namespace "urn:opendaylight:params:xml:ns:yang:topoprocessing:nt:provider:impl";
    prefix "nt-provider";

    import topoprocessing-provider {prefix topoproc;}
    import config {prefix config; revision-date 2013-04-05;}

    description
        "Topology Processing Network Topology Model module definition";

    revision "2015-08-19" {
        description
            "Initial revision";
    }

    identity topoprocessing-nt-provider-impl {
        base "config:module-type";
        config:java-name-prefix TopoProcessingNTProvider;
    }

    augment "/config:modules/config:module/config:configuration" {
        case topoprocessing-nt-provider-impl {
            when "/config:modules/config:module/config:type = 'topoprocessing-nt-provider-impl'";
            container topoprocessing-provider {
                uses config:service-ref {
                    refine type {
                        mandatory true;
                        config:required-identity topoproc:topoprocessing-provider;
                    }
                }
            }
        }
    }

}
