/*
 * Copyright (c) 2015 Pantheon Technologies s.r.o. and others.  All rights reserved.
 *
 * This program and the accompanying materials are made available under the
 * terms of the Eclipse Public License v1.0 which accompanies this distribution,
 * and is available at http://www.eclipse.org/legal/epl-v10.html
 */

 module topoprocessing-i2rs-provider-impl {
    yang-version 1;
    namespace "urn:opendaylight:params:xml:ns:yang:topoprocessing:i2rs:provider:impl";
    prefix "i2rs-provider";

    import topoprocessing-provider {prefix topoproc;}
    import config {prefix config; revision-date 2013-04-05;}

    description
        "Topology Processing I2RS Model module definition";

    revision "2015-08-19" {
        description
            "Initial revision";
    }

    identity topoprocessing-i2rs-provider-impl {
        base "config:module-type";
        config:java-name-prefix TopoProcessingI2rsProvider;
    }

    augment "/config:modules/config:module/config:configuration" {
        case topoprocessing-i2rs-provider-impl {
            when "/config:modules/config:module/config:type = 'topoprocessing-i2rs-provider-impl'";
            container topoprocessing-provider {
                uses config:service-ref {
                    refine type {
                        mandatory true;
                        config:required-identity topoproc:topoprocessing-provider;
                    }
                }
            }
        }
    }

}
