/*
 * Copyright (c) 2015 Pantheon Technologies s.r.o. and others. All rights reserved.
 *
 * This program and the accompanying materials are made available under the
 * terms of the Eclipse Public License v1.0 which accompanies this distribution,
 * and is available at http://www.eclipse.org/legal/epl-v10.html
 */

 module topoprocessing-provider-impl {
    yang-version 1;
    namespace "urn:opendaylight:params:xml:ns:yang:topoprocessing:provider:impl";
    prefix "topoprocessing-provider-impl";

    import topoprocessing-provider {prefix topoproc;}
    import config {prefix config; revision-date 2013-04-05;}

    description
        "Topology Processing Framework module definition";

    revision "2015-02-09" {
        description
            "Initial revision";
    }

    identity topoprocessing-provider-impl {
        base "config:module-type";
        config:provided-service topoproc:topoprocessing-provider;
        config:java-name-prefix TopoProcessingProvider;
    }

    augment "/config:modules/config:module/config:configuration" {
        case topoprocessing-provider-impl {
            when "/config:modules/config:module/config:type = 'topoprocessing-provider-impl'";
        }
    }

}
